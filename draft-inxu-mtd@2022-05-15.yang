module draft-inxu-mtd{
  yang-version 1.1;
  namespace "urn:ietf:params:xml:ns:yang:draft-inxu-mtd";
  prefix draft-inxu-mtd;

  import ietf-yang-types {
    prefix yang;
  }

  import ietf-access-control-list {
    prefix acl;
  }

  import ietf-inet-types {
    prefix inet;
  }

  import ietf-mud {
    prefix mud;
  }

  import ietf-acldns {
    prefix acldns;
  }

  organization "IETF IOTOPS (IOT Operations) Working Group";
  contact
    "WG Web: http://tools.ietf.org/wg/iotops/
     WG List: iotops@ietf.org
     Author: Sávyo Morais
     savyovm@gmail.com
     Author: Claudio Farias
     cmicelifarias@gmail.com";

  description 
    "This module is a data-model to describe malicious network 
    traffic.

    This module is intended to be serialized via JSON and stored
    as a file, as described in I-D draft-morais-iotops-inxu-01.

    The key words 'MUST', 'MUST NOT', 'REQUIRED', 'SHALL', 'SHALL
    NOT', 'SHOULD', 'SHOULD NOT', 'RECOMMENDED', 'NOT RECOMMENDED',
    'MAY', and 'OPTIONAL' in this document are to be interpreted as
    described in BCP 14 (RFC 2119) (RFC 8174) when, and only when,
    they appear in all capitals, as shown here.

    Copyright (c) 2022 IETF Trust and the persons identified as
    authors of the code.  All rights reserved.

    Redistribution and use in source and binary forms, with or
    without modification, is permitted pursuant to, and subject
    to the license terms contained in, the Simplified BSD License
    set forth in Section 4.c of the IETF Trust's Legal Provisions
    Relating to IETF Documents
    (http://trustee.ietf.org/license-info).

    This version of this YANG module is part of 
    I-D draft-morais-iotops-inxu-01; see the I-D itself for 
    full legal notices.";

  revision 2022-05-15{
    description
      "Simplifying the data model to one single description of 
      malicious traffic.";
    reference
      "draft-morais-iotops-inxu-01: Intra-Network eXposure analyzer 
                                    Utility Specification";
  }

  typedef action-to-take {
    description
      "Type to specify the action to take when a threat is detected";

    type enumeration {
      enum "alert" {
        value 0;
        description
          "Alert user about a risky exposure";
      }
      enum "block-not-attack" {
        value 1;
        description
          "Block risky exposures of not-attack-traffic and warns uses 
          about attack-traffic alert exposures";
      }
      enum "block-attack" {
        value 2;
        description
          "Block attack-traffic risky exposures and alert users about 
          the block";
      }
      enum "block-all" {
        value 3;
        description
          "Block all risky exposures and alert users about the block";
      }
    }
  }

  container mtd {
    presence "Enabled for this particular MTD URL";
    description "MTD-related information";
    uses mtd-groupig;
  }

  grouping mtd-groupig {
    description 
      "This grouping is to create a set of definitions of 
      malicious traffic of malware and attacks.";

    leaf mtd-url{
      type inet:uri;
      mandatory true;
      description 
        "This is the MTD URL associated with the entry found 
        in a MTD File";
    }

    leaf last-update {
      type yang:date-and-time;
      mandatory true;
      description 
        "This is intended to be set when the current MTD File is 
        generated. MTD Managers SHOULD NOT check for updates 
        between this time plus cache validity.";
    }

    leaf mtd-signature {
      type inet:uri;
      description 
        "A URI that resolves to a signature file to verify the 
        autenticity of the MTD File.";
     }

    leaf cache-validity {
      type uint8 {
        range "1..168";
      }

      units "hours";
      default "48";
      description 
        "The information retrieved from the MTD Server is
        valid for these many hours, after which it should be 
        refreshed. MTD Manager implementations do not need to
         discard MTD Files beyond this period.";
    }

    container malicious-descriptions {
      description 
        "This container has the descriptions of the malware and 
        attacks that can exploit or target the devices";

      uses malicious-list;
    }
  }

  grouping traffic-lists {
    description 
      "A grouping for acess lists of malicious traffic in the context 
      of malware or attacks.";

    container traffic-lists {
      description 
        "The access lists of the attack's malicious traffic 
        targeting or departing from the local IoT devices.";

      list traffic-list {
        key "name";

        description 
          "Each entry on this list refers to an malicious 
          traffic defined by an ACL that should present the
           overall network communication of the attack.";

        leaf name {
          type leafref{
            path "/acl:acls/acl:acl/acl:name";
          }

          description
            "The name of the ACL for this entry.";
        }

        leaf-list specific-devices {
          type inet:uri;

          description 
            "List of MUD URLs of specific devices 
            related with the vulnerability";
        }
      }
    }
  }

  grouping malicious-list {
    description 
      "A grouping for acess control lists of malicious traffic in the 
      context of malware or attacks.";

    list malicious-list {
      key "name";

      description 
        "The access lists of the malware's or attack's malicious 
        traffic targeting or departing from the local IoT devices,";

      leaf name {
        type string;

        description
          "The unique name of the described malicious activity for 
          each entry.";
      }

      leaf-list specific-devices {
        type inet:uri;

        description 
          "List of MUD URLs of specific devices 
          related with the vulnerability";
      }

      list critical-acl-sets{
        key "name";

        description
          "Each list entry represents a malicious activity's critical 
          set of risky ACL exposures, followed by the action to take 
          when a critical set be detected.";

        leaf name {
          type string;

          description
            "The critical ACL set name";
        }

        leaf-list critical-acl-set {
          type leafref{
            path "/acl:acls/acl:acl/acl:name";
          }

          description
            "A list to specify a set of ACLs that, when all listed 
            ACLs get classified as risky, represents a threat caused 
            by the malicious activity";
        }

        leaf action-to-take {
          type draft-inxu-mtd:action-to-take;
          mandatory true;
          description
            "A leaf to specify the action to be taken when 
            the respective set of critical ACLs turns into 
            a threat.";
        }
      }

      container to-device-attacks {
        description 
          "The set of attack traffic performed by the 
          infected IoT device";

        uses traffic-lists;
      }

      container from-device-attacks {
        description 
          "The set of attack traffic performed targeting 
          the infected IoT device";

        uses traffic-lists;
      }

      container to-device-not-attacks {
        description 
          "The set of attack traffic performed by the 
          infected IoT device";

        uses traffic-lists;
      }

      container from-device-not-attacks {
        description 
          "The set of attack traffic performed targeting 
          the infected IoT device";

        uses traffic-lists;
      }
    }
  }

  augment "/acl:acls/acl:acl/acl:aces/acl:ace/acl:matches" {
    description
      "adding abstraction to avoid the need of IP addresses.";
    container mtd {
      description
        "MTD-specific match.";
      leaf local-networks {
        type empty;
        description
          "IP addresses will match this node if they are
          considered local addresses. A local address may be
          a list of locally defined prefixes and masks
          that indicate a particular administrative scope.";
      }
    }
  }

  augment "/acl:acls/acl:acl/acl:aces/acl:ace" {
    description
      "Add the risk level information associated to the ACE";
    leaf risk {
      type uint8;
      default "1";
      description
        "Represents risk level of a device being exploited
        when exposes the device through traffic matching the 
        described ACE.";
    }

  }

  augment "/acl:acls/acl:acl" {
    description
      "Add an acceptable risk threshold and an alert risk threshold 
      to the ACL";
    leaf risk-threshold {
      type uint8;
      default "1";
      description
        "The acceptable risk threshold represents the minimum 
        risk value for the exposure be considered a risk.
        The actual risk of an ACL is calculated by the sum of 
        all the ACEs that matched on the INXU Module analysis";
    }

    leaf alert-threshold {
      type uint8;
      default "1";
      description
        "The acceptable alert threshold represents the minimum 
        risk value for the exposure trigger an alert.
        The actual risk of an ACL is calculated by the sum of 
        all the ACEs that matched on the INXU Module analysis";
    }
  }

  augment "/acl:acls/acl:acl/acl:aces/acl:ace/acl:matches"
    + "/acl:l4/acl:tcp/acl:tcp" {
    description
      "Add direction-initiated";
    leaf direction-initiated {
      type mud:direction;
      description
        "This node matches based on which direction a
        connection was initiated.";
       }
  }

  augment "/acl:acls/acl:acl/acl:aces/acl:ace/acl:matches" 
    + "/acl:l3/acl:ipv4/acl:ipv4" {
    description
      "Adding domain names to matching.";
    uses acldns:dns-matches;
  }
  
  augment "/acl:acls/acl:acl/acl:aces/acl:ace/acl:matches" 
    + "/acl:l3/acl:ipv6/acl:ipv6" {
    description
      "Adding domain names to matching.";
    uses acldns:dns-matches;
  }

  deviation "/acl:acls/acl:acl/acl:aces/acl:ace/acl:actions" {
    deviate not-supported;
    description
      "Field not used in this specification";
  }
}
